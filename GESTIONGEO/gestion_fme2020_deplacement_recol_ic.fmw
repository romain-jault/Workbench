FME workspace gestion_fme2020_deplacement_recol_ic.fmw

Parameters:
- TEXT = 46437   # ID_DOS NUMERO DU DOSSIER ASSOCIE AU FICHIER
- FILENAME_MUSTEXIST = P:\UF_Acquisition\test_gestiongeo\TEST_COPIE_DANS_ZIP.pdf   # FICHIER_A_DEPLACER *|* FICHIER A DEPLACER
- UTILISATEUR_G_GESTIONGEO_MAJ = G_GESTIONGEO_MAJ   # UTILISATEUR G_GESTIONGEO_MAJ
- INSTANCE_DEVELOPPEMENT_MULTIT = MULTIT   # INSTANCE DEVELOPPEMENT MULTIT
- MDP_DEVELLOPEMENT_G_GESTIONGEO_MAJ =   # MDP DEVELOPPEMENT G_GESTIONGEO_MAJ
- REPERTOIRE = /var/www/extraction/apps/gestiongeo

Writers:
- FILECOPY_1: FILECOPY to IC
- ORACLE_NONSPATIAL_1: ORACLE_NONSPATIAL to $(INSTANCE_DEVELOPPEMENT_MULTIT)

Creator
    GEOMTYPE = Geometry Object
    NUM = 1
    CREATED -> AttributeCreator_4
AttributeCreator_4
    ATTR_TABLE = SET_TO fichier_source = $(FICHIER_A_DEPLACER)
    -> FilenamePartExtractor
Note: Extraction du chemin pour determiner le chemin, le nom, l'extension et les caractéristiques du fichier à déplacer.
FilenamePartExtractor
    DIRNAME_ATTR = _dirname
    DIRPATH_ATTR = _dirpath
    EXTENSION_ATTR = _extension
    FULLNAME_ATTR = _filename
    ROOTNAME_ATTR = _rootname
    SRC_ATTR = @Value(fichier_source)
    -> AttributeCreator
Note: Creation de l'attribut ID_DOS
AttributeCreator
    ATTR_TABLE = SET_TO ID_DOS = $(ID_DOS)
    -> AttributeCreator_2
Note: Création des attribut pour les writers filecopy: / - nom_fichier: nom du fichier de sortir / - chemin_fichier: chemin de sortie du fichier / - source_fichier: fichier original / - DOS_URL_FILE: chemin_fichier/nom_fichier / création de l'attribut FILE_INTEGRATION_TOPO / - 0: fichier attaché au dossier. Mais non intégré
AttributeCreator_2
    ATTR_TABLE:
      SET_TO nom_fichier = @Value(_rootname).@Value(_extension)
      SET_TO chemin_fichier = \$(REPERTOIRE)\$(ID_DOS)
      SET_TO INTEGRATION = 0
      SET_TO DOS_URL_FILE = $(REPERTOIRE)\$(ID_DOS)\@Value(_rootname).@Value(_extension)
      SET_TO ID_DOS = $(ID_DOS)
    -> DatabaseJoiner_2
Note: Vérifie que pour un fichier attaché au dossier, celui-ci n'est pas déjà dans la table.
DatabaseJoiner_2
    ATTR_ACCUM_MODE = Merge Joined
    ATTR_CONFLICT_RES = Use Original
    CACHE_SIZE = 5000
    DATASET = $(INSTANCE_DEVELOPPEMENT_MULTIT)
    FORMAT = ORACLE_SPATIAL
    JOINED_LIST_NAME = _join_list
    JOIN_KEYS = ID_DOS FID_DOSSIER DOS_URL_FILE DOS_URL_FILE
    MATCH_MULTIPLE_DISPLAY = Add fields on a list attribute
    MATCH_RULE_DISPLAY = Match All (1:M)
    ORACLE_SPATIAL_CREATE_FEATURE_TABLES_FROM_DATA = Yes
    ORACLE_SPATIAL_PASSWORD = $(MDP_DEVELLOPEMENT_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    PREFETCH_EXHAUSTIVE = Yes
    TABLE = G_GESTIONGEO.TA_GG_URL_FILE
    UNJOINED -> filecopy (writer FILECOPY_1)
    UNJOINED -> G_GESTIONGEO.TA_GG_URL_FILE (writer ORACLE_NONSPATIAL_1)
Note: copie du fichie dans le repertoire IC ou RECOL.
filecopy (writer FILECOPY_1)
    attributes: filecopy_source_dataset char(512), filecopy_dest_dataset char(512), filecopy_dest_filename char(128)
Note: Insertion des éléments dans la table TA_GG_URL_FILE.
G_GESTIONGEO.TA_GG_URL_FILE (writer ORACLE_NONSPATIAL_1)
    attributes: DOS_URL_FILE varchar2(200), FID_DOSSIER varchar2(200), INTEGRATION varchar2(200)
